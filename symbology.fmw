FME workspace symbology.fmw

Parameters:
- DestDataset_GEOJSON =
- SourceDataset_GEOJSON =

Readers:
- GEOJSON_1: GEOJSON from $(SourceDataset_GEOJSON)

Writers:
- GEOJSON_2: GEOJSON to $(DestDataset_GEOJSON)

RIO_Verdeling (reader GEOJSON_1)
    attributes: Gemeentenaam string, RIO string, Grootteklasse string, Provincienaam string, Samenwerkingsverband string, Veiligheidsregio's string, Omgevingsdiensten string, Waterschap string
    -> AttributeCreator
AttributeCreator
    ATTR_TABLE = SET_TO fill = FME_CONDITIONAL:DEFAULT_VALUE'_FME_NO_OP_'BOOL_OP;OR;COMPOSITE_TEST;1;TEST @Value(Provincienaam) = Drenthe'#FF0000'BOOL_OP;OR;COMPOSITE_TEST;1;TEST @Value(Provincienaam) = Flevoland'#FF8000'BOOL_OP;OR;COMPOSITE_TEST;1;TEST @Value(Provincienaam) = Friesland'#FFFF00'BOOL_OP;OR;COMPOSITE_TEST;1;TEST @Value(Provincienaam) = Gelderland'#80FF00'BOOL_OP;OR;COMPOSITE_TEST;1;TEST @Value(Provincienaam) = Groningen'#00FFFF'BOOL_OP;OR;COMPOSITE_TEST;1;TEST @Value(Provincienaam) = Limburg'#00FF00'BOOL_OP;OR;COMPOSITE_TEST;1;TEST @Value(Provincienaam) = Noord-Brabant'#0000FF'BOOL_OP;OR;COMPOSITE_TEST;1;TEST @Value(Provincienaam) = Noord-Holland'#0080FF'BOOL_OP;OR;COMPOSITE_TEST;1;TEST @Value(Provincienaam) = Overijssel'#7F00FF'BOOL_OP;OR;COMPOSITE_TEST;1;TEST @Value(Provincienaam) = Utrecht'#808080'BOOL_OP;OR;COMPOSITE_TEST;1;TEST @Value(Provincienaam) = Zeeland'#FF007F'BOOL_OP;OR;COMPOSITE_TEST;1;TEST @Value(Provincienaam) = Zuid-Holland'#660033'FME_NUM_CONDITIONS13___
    -> AttributeManager
AttributeManager
    -> RIO_Verdeling (writer GEOJSON_2)
RIO_Verdeling (writer GEOJSON_2)
    attributes: Gemeentenaam string, RIO string, Grootteklasse string, Provincienaam string, Samenwerkingsverband string, Veiligheidsregio's string, Omgevingsdiensten string, Waterschap string, fill string
